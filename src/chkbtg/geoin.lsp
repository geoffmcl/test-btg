(defun check-header (line / return)
	(setq return 0)
	(if (= line "LAYER") (setq return 1))
	(if (= line "BSPHERE") (setq return 2))
	(if (= line "POINTS") (setq return 3))
	(if (= line "TRIANGLES") (setq return 4))
	(if (= line "STRIPES") (setq return 5))
	(if (= line "FANS") (setq return 6))
	return
)

(defun read-coo( line / koo len start count char)
	(setq len (strlen line) start 1 count 1 koo nil)
	(while (/= (setq char (substr line count 1)) "")
		(if (= char ",")
			(progn
;;				(princ "found: ") (princ (substr line start (- count start))) (princ "\n")
				(setq koo (append koo (list (atof (substr line start (- count start))))))
				(setq start (1+ count))
			)
		)
		(setq count (1+ count))
	)
;;	(princ "last : ") (princ (substr line start (- count start))) (princ "\n")
	(setq koo (append koo (list (atof (substr line start)))))
	koo
)



(defun c:geoin ( / filename file line type now layer koo1 koo2 koo3 bs rad)
	(setq filename (getfiled "Select the GEO-File" "" "geo" 0))
	(setq file (open filename "r"))

	(while 
		(setq line (read-line file))
;;		(princ line)(princ "\n")
		(setq type (check-header line))
		(if (= type 0)
			(progn
				(setq koo (read-coo line))
;;				(princ "Koo: ") (princ koo) (princ "\n")
				(if (= now 2)
					(progn
						(setq bs koo)
						(entmake (list
							(cons 0 "CIRCLE")
							(cons 8 layer)
							(cons 10 (list (car bs) (cadr bs) (caddr bs)))
							(cons 40 (cadddr koo))
						));end_list end_entmake
						(entmake (list
							(cons 0 "LINE")
							(cons 8 layer)
							(cons 10  (list 0.0 0.0 0.0))
							(cons 11 (list (car bs) (cadr bs) (caddr bs)))
						));end_list end_entmake
;;						(princ "insert Bounding Sphere\n")
					)
				)
				(if (= now 3)
					(progn
						(entmake (list
							(cons 0 "POINT")
							(cons 8 layer)
;							(cons 10 (list (car koo) (cadr koo) (caddr koo)))
							(cons 10 (list (+ (car bs) (car koo)) (+ (cadr bs) (cadr koo)) (+ (caddr bs) (caddr koo))))
						));end_list end_entmake
;;						(princ "insert Point\n")
						(setq koo1 nil koo2 nil koo3 nil)
					)
				)
				(if (= now 4)
					(progn
						(if (= nil koo1)
							(progn
								(setq koo1 koo)
;;								(princ "set koo1\n")
							)
							(if (= nil koo2)
								(progn
									(setq koo2 koo)
;;									(princ "set koo2\n")
								)
								(if (= nil koo3)
									(progn
										(setq koo3 koo)
;;										(princ "set koo3\n")
									)
								)
							)
						)
						(if (and (/= koo1 nil) (/= koo2 nil) (/= koo3 nil))
							(progn
								(entmake (list
									(cons 0 "3DFACE")
									(cons 8 layer)
;									(cons 10 (list (car koo1) (cadr koo1) (caddr koo1)))
;									(cons 11 (list (car koo2) (cadr koo2) (caddr koo2)))
;									(cons 12 (list (car koo3) (cadr koo3) (caddr koo3)))
;									(cons 13 (list (car koo3) (cadr koo3) (caddr koo3)))
									(cons 10 (list (+ (car bs) (car koo1)) (+ (cadr bs) (cadr koo1)) (+ (caddr bs) (caddr koo1))))
									(cons 11 (list (+ (car bs) (car koo2)) (+ (cadr bs) (cadr koo2)) (+ (caddr bs) (caddr koo2))))
									(cons 12 (list (+ (car bs) (car koo3)) (+ (cadr bs) (cadr koo3)) (+ (caddr bs) (caddr koo3))))
									(cons 13 (list (+ (car bs) (car koo3)) (+ (cadr bs) (cadr koo3)) (+ (caddr bs) (caddr koo3))))
									(cons 70 0)
								));end_list end_entmake
;;								(princ "insert 3dface\n")
								(setq koo1 nil koo2 nil koo3 nil)
							)
						)
					)
				)
				(if (= now 5)
					(progn
						(if (= nil koo1)
							(progn
								(setq koo1 koo)
;;								(princ "set koo1\n")
							)
							(if (= nil koo2)
								(progn
									(setq koo2 koo)
;;									(princ "set koo2\n")
								)
								(if (= nil koo3)
									(progn
										(setq koo3 koo)
;;										(princ "set koo3\n")
									)
								)
							)
						)
						(if (and (/= koo1 nil) (/= koo2 nil) (/= koo3 nil))
							(progn
								(entmake (list
									(cons 0 "3DFACE")
									(cons 8 layer)
;									(cons 10 (list (car koo1) (cadr koo1) (caddr koo1)))
;									(cons 11 (list (car koo2) (cadr koo2) (caddr koo2)))
;									(cons 12 (list (car koo3) (cadr koo3) (caddr koo3)))
;									(cons 13 (list (car koo3) (cadr koo3) (caddr koo3)))
									(cons 10 (list (+ (car bs) (car koo1)) (+ (cadr bs) (cadr koo1)) (+ (caddr bs) (caddr koo1))))
									(cons 11 (list (+ (car bs) (car koo2)) (+ (cadr bs) (cadr koo2)) (+ (caddr bs) (caddr koo2))))
									(cons 12 (list (+ (car bs) (car koo3)) (+ (cadr bs) (cadr koo3)) (+ (caddr bs) (caddr koo3))))
									(cons 13 (list (+ (car bs) (car koo3)) (+ (cadr bs) (cadr koo3)) (+ (caddr bs) (caddr koo3))))
									(cons 70 0)
								));end_list end_entmake
;;								(princ "insert 3dface\n")
								(setq koo1 koo2)
								(setq koo2 koo3)
								(setq koo3 nil)
							)
						)
					)
				)
				(if (= now 6)
					(progn
						(if (= nil koo1)
							(progn
								(setq koo1 koo)
;;								(princ "set koo1\n")
							)
							(if (= nil koo2)
								(progn
									(setq koo2 koo)
;;									(princ "set koo2\n")
								)
								(if (= nil koo3)
									(progn
										(setq koo3 koo)
;;										(princ "set koo3\n")
									)
								)
							)
						)
						(if (and (/= koo1 nil) (/= koo2 nil) (/= koo3 nil))
							(progn
								(entmake (list
									(cons 0 "3DFACE")
									(cons 8 layer)
;									(cons 10 (list (car koo1) (cadr koo1) (caddr koo1)))
;									(cons 11 (list (car koo2) (cadr koo2) (caddr koo2)))
;									(cons 12 (list (car koo3) (cadr koo3) (caddr koo3)))
;									(cons 13 (list (car koo3) (cadr koo3) (caddr koo3)))
									(cons 10 (list (+ (car bs) (car koo1)) (+ (cadr bs) (cadr koo1))) (+ (caddr bs) (caddr koo1)))
									(cons 11 (list (+ (car bs) (car koo2)) (+ (cadr bs) (cadr koo2))) (+ (caddr bs) (caddr koo2)))
									(cons 12 (list (+ (car bs) (car koo3)) (+ (cadr bs) (cadr koo3))) (+ (caddr bs) (caddr koo3)))
									(cons 13 (list (+ (car bs) (car koo3)) (+ (cadr bs) (cadr koo3))) (+ (caddr bs) (caddr koo3)))
									(cons 70 0)
								));end_list end_entmake
;;								(princ "insert 3dface\n")
								(setq koo2 koo3)
								(setq koo3 nil)
							)
						)
					)
				)
			)
			(setq koo1 nil koo2 nil koo3 nil rad nil now 0)
		)
		(if (= type 1) (setq layer (read-line file)))
		(if (= type 2) (setq now 2))
		(if (= type 3) (setq now 3))
		(if (= type 4) (setq now 4))
		(if (= type 5) (setq now 5))
		(if (= type 6) (setq now 6))
	)
	(close file)
	(princ)
)
